/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULLayerHandler.ulp generated on 17/17/13 13:16:03 */

#include "ULSupport.ulp"

string ULLayerHandler(UL_LAYER Layer,string currentPath, string argument, char cacheMode)
{
	string baseName = GetFirstPathItem(currentPath);
	string nextPath = GetNextPath(currentPath);
	string baseType = GetFirstPathItem(nextPath);

	char   nextCacheMode = cacheMode;
	string cacheResult;

	
	if (cacheMode == CACHE_MODE_THIS)
	{
		cacheResult += intToStr(Layer.color) + "?";
		cacheResult += intToStr(Layer.fill) + "?";
		cacheResult += Layer.name  + "?";
		cacheResult += intToStr(Layer.number) + "?";
		cacheResult += intToStr(Layer.used) + "?";
		cacheResult += intToStr(Layer.visible) + "?";
		return cacheResult;
	}	
	else if (baseName == "color")
		return intToStr(Layer.color);
	else if (baseName == "fill")
		return intToStr(Layer.fill);
	else if (baseName == "name")
		return Layer.name;
	else if (baseName == "number")
		return intToStr(Layer.number);
	else if (baseName == "used")
		return intToStr(Layer.used);
	else if (baseName == "visible")
		return intToStr(Layer.visible);
		
	return "ERROR:" + intToStr(ERROR_LAYER_HANDLER);
}
