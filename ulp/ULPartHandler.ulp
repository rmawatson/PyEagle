/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULPartHandler.ulp generated on 17/17/13 13:16:03 */

#include "ULSupport.ulp"
#include "ULDeviceHandler.ulp"
#include "ULDeviceSetHandler.ulp"
#include "ULAttributeHandler.ulp"
#include "ULInstanceHandler.ulp"
#include "ULVariantHandler.ulp"

string ULPartHandler(UL_PART Part, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += Part.name + "?";
		cacheResult += intToStr(Part.populate) + "?";
		cacheResult += Part.value + "?";
		return cacheResult;
	}
	else if (baseName == "attribute")
		return Part.attribute[argument];
	else if (baseName == "device")
		return ULDeviceHandler(Part.device,nextPath,argument,0);		
	else if (baseName == "deviceset")
		return ULDeviceSetHandler(Part.deviceset,nextPath,argument,0);	
	else if (baseName == "name")
		return Part.name;
	else if (baseName == "populate")
		return intToStr(Part.populate);
	else if (baseName == "value")
		return Part.value;		
		
		
		
	string splitLoopMember[];
	int accessIndex=0,currentIndex=0;
	
	if (!isLastPath)
	{	
	    nextPath = GetNextPath(nextPath);
		strsplit(splitLoopMember,baseType,'^');
		accessIndex = strtol(splitLoopMember[1]);
	}
	if (baseName == "attributes"){
		Part.attributes(Attribute)  { 
			if (!isLastPath){ if (currentIndex  == accessIndex) { return ULAttributeHandler(Attribute, nextPath,argument,0); } }
			else if (nextCacheMode==CACHE_MODE_THIS) { cacheResult += ":" + ULAttributeHandler(Attribute, "", "",CACHE_MODE_THIS); } 
			currentIndex++;
		}
		if (nextCacheMode==CACHE_MODE_THIS) return cacheResult;
		else return intToStr(currentIndex);
	
	} else if (baseName == "instances"){
		Part.instances(Instance)  { 
			if (!isLastPath){ if (currentIndex  == accessIndex) { return ULInstanceHandler(Instance, nextPath,argument,0); } }
			else if (nextCacheMode==CACHE_MODE_THIS) { cacheResult += ":" + ULInstanceHandler(Instance, "", "",CACHE_MODE_THIS); } 
			currentIndex++;
		}
		if (nextCacheMode==CACHE_MODE_THIS) return cacheResult;
		else return intToStr(currentIndex);
	
	} else if (baseName == "variants"){
		Part.variants(Variant)  { 
			if (!isLastPath){ if (currentIndex  == accessIndex) { return ULVariantHandler(Variant, nextPath,argument,0); } }
			else if (nextCacheMode==CACHE_MODE_THIS) { cacheResult += ":" + ULVariantHandler(Variant, "", "",CACHE_MODE_THIS); } 
			currentIndex++;
		}
		if (nextCacheMode==CACHE_MODE_THIS) return cacheResult;
		else return intToStr(currentIndex);
	
	} 
	return "ERROR:" + intToStr(ERROR_PART_HANDLER);
}
