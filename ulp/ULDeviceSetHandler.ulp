/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULDeviceSetHandler.ulp generated on 17/17/13 13:16:03 */

#include "ULSupport.ulp"
#include "ULDeviceHandler.ulp"
#include "ULAreaHandler.ulp"
#include "ULDeviceHandler.ulp"
#include "ULGateHandler.ulp"

string ULDeviceSetHandler(UL_DEVICESET DeviceSet, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += DeviceSet.description + "?";
		cacheResult += DeviceSet.headline + "?";
		cacheResult += DeviceSet.library + "?";
		cacheResult += DeviceSet.name + "?";
		cacheResult += DeviceSet.prefix + "?";
		cacheResult += DeviceSet.value + "?";
		return cacheResult;
	}
	else if (baseName == "activedevice")
		return ULDeviceHandler(DeviceSet.activedevice,nextPath,argument,0);		
	else if (baseName == "area")
		return ULAreaHandler(DeviceSet.area,nextPath,argument,0);		
	else if (baseName == "description")
		return DeviceSet.description;
	else if (baseName == "headline")
		return DeviceSet.headline;
	else if (baseName == "library")
		return DeviceSet.library;
	else if (baseName == "name")
		return DeviceSet.name;
	else if (baseName == "prefix")
		return DeviceSet.prefix;
	else if (baseName == "value")
		return DeviceSet.value;
		
	string splitLoopMember[];
	int accessIndex=0,currentIndex=0;
	
	if (!isLastPath)
	{	
	    nextPath = GetNextPath(nextPath);
		strsplit(splitLoopMember,baseType,'^');
		accessIndex = strtol(splitLoopMember[1]);
	}

	if (baseName == "devices"){
		DeviceSet.devices(Device)  { 
			if (!isLastPath){ if (currentIndex  == accessIndex) { return ULDeviceHandler(Device, nextPath,argument,0); } }
			else if (nextCacheMode==CACHE_MODE_THIS) { cacheResult += ":" + ULDeviceHandler(Device, "", "",CACHE_MODE_THIS); } 
			currentIndex++;
		}
		if (nextCacheMode==CACHE_MODE_THIS) return cacheResult;
		else return intToStr(currentIndex);
	
	} else if (baseName == "gates"){
		DeviceSet.gates(Gate)  { 
			if (!isLastPath){ if (currentIndex  == accessIndex) { return ULGateHandler(Gate, nextPath,argument,0); } }
			else if (nextCacheMode==CACHE_MODE_THIS) { cacheResult += ":" + ULGateHandler(Gate, "", "",CACHE_MODE_THIS); } 
			currentIndex++;
		}
		if (nextCacheMode==CACHE_MODE_THIS) return cacheResult;
		else return intToStr(currentIndex);
	
	} 
	
	return "ERROR:" + intToStr(ERROR_DEVICESET_HANDLER);
}
