/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULNetHandler.ulp generated on 17/17/13 13:16:03 */

#include "ULSupport.ulp"
#include "ULClassHandler.ulp"
#include "ULPinRefHandler.ulp"
#include "ULSegmentHandler.ulp"

string ULNetHandler(UL_NET Net, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		//cacheResult += Net.column + "?"; Cant access net column with out a sheet context
		cacheResult += "?";
		cacheResult += Net.name + "?";
		cacheResult += "?";
		//cacheResult += Net.column + "?"; Cant access net column with out a sheet context
		return cacheResult;
	}
	else if (baseName == "class")
		return ULClassHandler(Net.class,nextPath,argument,0);	
	else if (baseName == "column")
		return Net.column;
	else if (baseName == "name")
		return Net.name;
	else if (baseName == "row")
		return Net.row;

	string splitLoopMember[];
	int accessIndex=0,currentIndex=0;
	
	if (!isLastPath)
	{	
	    nextPath = GetNextPath(nextPath);
		strsplit(splitLoopMember,baseType,'^');
		accessIndex = strtol(splitLoopMember[1]);
	}

	if (baseName == "pinrefs"){
		Net.pinrefs(PinRef)  { 
			if (!isLastPath){ if (currentIndex  == accessIndex) { return ULPinRefHandler(PinRef, nextPath,argument,0); } }
			else if (nextCacheMode==CACHE_MODE_THIS) { cacheResult += ":" + ULPinRefHandler(PinRef, "", "",CACHE_MODE_THIS); } 
			currentIndex++;
		}
		if (nextCacheMode==CACHE_MODE_THIS) return cacheResult;
		else return intToStr(currentIndex);
	
	} else if (baseName == "segments"){
		Net.segments(Segment)  { 
			if (!isLastPath){ if (currentIndex  == accessIndex) { return ULSegmentHandler(Segment, nextPath,argument,0); } }
			else if (nextCacheMode==CACHE_MODE_THIS) { cacheResult += ":" + ULSegmentHandler(Segment, "", "",CACHE_MODE_THIS); } 
			currentIndex++;
		}
		if (nextCacheMode==CACHE_MODE_THIS) return cacheResult;
		else return intToStr(currentIndex);

	} 
	return "ERROR:" + intToStr(ERROR_NET_HANDLER);
}
