/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULArcHandler.ulp generated on 17/17/13 13:16:03 */

#include "ULSupport.ulp"

string ULArcHandler(UL_ARC Arc,string currentPath, string argument, char cacheMode)
{
	string baseName   = GetFirstPathItem(currentPath);
	string nextPath   = GetNextPath(currentPath);
	string baseType = GetFirstPathItem(nextPath);
	string cacheResult;

    if (cacheMode == CACHE_MODE_THIS)
	{
		cacheResult += realToStr(Arc.angle1) + "?";
		cacheResult += realToStr(Arc.angle2) + "?";
		cacheResult += intToStr(Arc.cap) + "?";
		cacheResult += intToStr(Arc.layer) + "?";
		cacheResult += intToStr(Arc.radius) + "?";
		cacheResult += intToStr(Arc.width) + "?";
		cacheResult += intToStr(Arc.x1) + "?";
		cacheResult += intToStr(Arc.x2) + "?";
		cacheResult += intToStr(Arc.xc) + "?";
		cacheResult += intToStr(Arc.y1) + "?";
		cacheResult += intToStr(Arc.y2) + "?";
		cacheResult += intToStr(Arc.yc) + "?";
		return cacheResult;
	}
	else if (baseName == "angle1")
		return realToStr(Arc.angle1);
	else if (baseName == "angle2")
		return realToStr(Arc.angle2);
	else if (baseName == "cap")
		return intToStr(Arc.cap);
	else if (baseName == "layer")
		return intToStr(Arc.layer);
	else if (baseName == "radius")
		return intToStr(Arc.radius);
	else if (baseName == "width")
		return intToStr(Arc.width);	
	else if (baseName == "x1")
		return intToStr(Arc.x1);
	else if (baseName == "x2")
		return intToStr(Arc.x2);
	else if (baseName == "xc")
		return intToStr(Arc.xc);			
	else if (baseName == "y1")
		return intToStr(Arc.y1);
	else if (baseName == "y2")
		return intToStr(Arc.y2);
	else if (baseName == "yc")
		return intToStr(Arc.yc);
		
	return "ERROR:" + intToStr(ERROR_ARC_HANDLER);
}
