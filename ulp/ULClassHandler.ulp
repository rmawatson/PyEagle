/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULClassHandler.ulp generated on 17/17/13 13:16:03 */

#include "ULSupport.ulp"

string ULClassHandler(UL_CLASS Class,string currentPath, string argument, char cacheMode)
{
	string baseName = GetFirstPathItem(currentPath);
	string nextPath = GetNextPath(currentPath);
	string baseType = GetFirstPathItem(nextPath);
	string cacheResult;

    if (cacheMode == CACHE_MODE_THIS)
	{
		cacheResult += intToStr(Class.clearance) + "?";
		cacheResult += intToStr(Class.drill) + "?";
		cacheResult += Class.name + "?";
		cacheResult += intToStr(Class.number) + "?";
		cacheResult += intToStr(Class.width) + "?";
		return cacheResult;
	}
	else if (baseName == "clearance")
		return intToStr(Class.clearance);
	else if (baseName == "drill")
		return intToStr(Class.drill);
	else if (baseName == "name")
		return Class.name;
	else if (baseName == "number")
		return intToStr(Class.number);
	else if (baseName == "width")
		return intToStr(Class.width);
		
	return "ERROR:" + intToStr(ERROR_CLASS_HANDLER);
}
