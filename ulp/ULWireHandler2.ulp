/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULWireHandler2.ulp generated on 17/17/13 13:16:03 */

#include "ULSupport.ulp"
#include "ULArcHandler.ulp"

string ULWireHandler2(UL_WIRE Wire,string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += intToStr(Wire.cap) + "?";
		cacheResult += realToStr(Wire.curve) + "?";
		cacheResult += intToStr(Wire.layer) + "?";
		cacheResult += intToStr(Wire.style) + "?";
		cacheResult += intToStr(Wire.width) + "?";
		cacheResult += intToStr(Wire.x1) + "?";
		cacheResult += intToStr(Wire.x2) + "?";
		cacheResult += intToStr(Wire.y1) + "?";
		cacheResult += intToStr(Wire.y2) + "?";
		return cacheResult;
	}
	else if (baseName == "arc")
		return ULArcHandler(Wire.arc,nextPath, argument,0);
	else if (baseName == "cap")
		return intToStr(Wire.cap);
	else if (baseName == "curve")
		return realToStr(Wire.curve);
	else if (baseName == "layer")
		return intToStr(Wire.layer);
	else if (baseName == "style")
		return intToStr(Wire.style);
	else if (baseName == "width")
		return intToStr(Wire.width);
	else if (baseName == "x1")
		return intToStr(Wire.x1);
	else if (baseName == "x2")
		return intToStr(Wire.x2);	
	else if (baseName == "y1")
		return intToStr(Wire.y1);
	else if (baseName == "y2")
		return intToStr(Wire.y2);
		
	string splitLoopMember[];
	int accessIndex=0,currentIndex=0;
	
	if (!isLastPath)
	{	
	    nextPath = GetNextPath(nextPath);
		strsplit(splitLoopMember,baseType,'^');
		accessIndex = strtol(splitLoopMember[1]);
	}

	if (baseName == "pieces"){
		Wire.pieces(WirePiece)  { 
			if (!isLastPath){ if (currentIndex  == accessIndex) { return intToStr(ERROR_MAX_DEPTH); } }
			else if (nextCacheMode==CACHE_MODE_THIS) {cacheResult += ""; } 
			currentIndex++;
		}
		if (nextCacheMode==CACHE_MODE_THIS) return cacheResult;
		else return intToStr(currentIndex);
	
	} 
	return "ERROR:" + intToStr(ERROR_WIRE_HANDLER);
}
