/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULSegmentHandler.ulp generated on 17/17/13 13:16:03 */

#include "ULSupport.ulp"
#include "ULJunctionHandler.ulp"
#include "ULLabelHandler.ulp"
#include "ULPinRefHandler.ulp"
#include "ULTextHandler.ulp"
#include "ULWireHandler.ulp"

string ULSegmentHandler(UL_SEGMENT Segment, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        
	
	string splitLoopMember[];
	int accessIndex=0,currentIndex=0;
	
	if (!isLastPath)
	{	
	    nextPath = GetNextPath(nextPath);
		strsplit(splitLoopMember,baseType,'^');
		accessIndex = strtol(splitLoopMember[1]);
	}

	if (baseName == "junctions"){
		Segment.junctions(Junction)  { 
			if (!isLastPath){ if (currentIndex  == accessIndex) { return ULJunctionHandler(Junction, nextPath,argument,0); } }
			else if (nextCacheMode==CACHE_MODE_THIS) { cacheResult += ":" + ULJunctionHandler(Junction, "", "",CACHE_MODE_THIS); } 
			currentIndex++;
		}
		if (nextCacheMode==CACHE_MODE_THIS) return cacheResult;
		else return intToStr(currentIndex);
	
	} else if (baseName == "labels"){
		Segment.labels(Label)  { 
			if (!isLastPath){ if (currentIndex  == accessIndex) { return ULLabelHandler(Label, nextPath,argument,0); } }
			else if (nextCacheMode==CACHE_MODE_THIS) { cacheResult += ":" + ULLabelHandler(Label, "", "",CACHE_MODE_THIS); } 
			currentIndex++;
		}
		if (nextCacheMode==CACHE_MODE_THIS) return cacheResult;
		else return intToStr(currentIndex);
	
	} else if (baseName == "pinrefs"){
		Segment.pinrefs(PinRef)  { 
			if (!isLastPath){ if (currentIndex  == accessIndex) { return ULPinRefHandler(PinRef, nextPath,argument,0); } }
			else if (nextCacheMode==CACHE_MODE_THIS) { cacheResult += ":" + ULPinRefHandler(PinRef, "", "",CACHE_MODE_THIS); } 
			currentIndex++;
		}
		if (nextCacheMode==CACHE_MODE_THIS) return cacheResult;
		else return intToStr(currentIndex);
	
	} else if (baseName == "texts"){
		Segment.texts(Text)  { 
			if (!isLastPath){ if (currentIndex  == accessIndex) { return ULTextHandler(Text, nextPath,argument,0); } }
			else if (nextCacheMode==CACHE_MODE_THIS) { cacheResult += ":" + ULTextHandler(Text, "", "",CACHE_MODE_THIS); } 
			currentIndex++;
		}
		if (nextCacheMode==CACHE_MODE_THIS) return cacheResult;
		else return intToStr(currentIndex);
	
	} else if (baseName == "wires"){
		Segment.wires(Wire)  { 
			if (!isLastPath){ if (currentIndex  == accessIndex) { return ULWireHandler(Wire, nextPath,argument,0); } }
			else if (nextCacheMode==CACHE_MODE_THIS) { cacheResult += ":" + ULWireHandler(Wire, "", "",CACHE_MODE_THIS); } 
			currentIndex++;
		}
		if (nextCacheMode==CACHE_MODE_THIS) return cacheResult;
		else return intToStr(currentIndex);
	
	} 
	
	return "ERROR:" + intToStr(ERROR_SEGMENT_HANDLER);
}
