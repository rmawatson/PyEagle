/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULVariantHandler.ulp generated on 17/17/13 13:16:03 */

#include "ULSupport.ulp"
#include "ULVariantDefHandler.ulp"

string ULVariantHandler(UL_VARIANT Variant,string currentPath, string argument, char cacheMode)
{
	string baseName = GetFirstPathItem(currentPath);
	string nextPath = GetNextPath(currentPath);
	string baseType = GetFirstPathItem(nextPath);
	string cacheResult;

    if (cacheMode == CACHE_MODE_THIS)
	{
		cacheResult += intToStr(Variant.populate) + "?";
		cacheResult += Variant.value + "?";
		cacheResult += Variant.technology + "?";
		return cacheResult;
	}
	else if (baseName == "populate")
		return intToStr(Variant.populate);
	else if (baseName == "value")
		return Variant.value;
	else if (baseName == "technology")
		return Variant.technology;
	else if (baseName == "variantdef")
		return ULVariantDefHandler(Variant.variantdef,nextPath,argument,0);
		
	return "ERROR:" + intToStr(ERROR_VARIANT_HANDLER);
}
