/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULDeviceHandler.ulp generated on 17/17/13 13:16:03 */

#include "ULSupport.ulp"
#include "ULAreaHandler.ulp"
#include "ULPackageHandler.ulp"
#include "ULAttributeHandler.ulp"
#include "ULGateHandler.ulp"

string ULDeviceHandler(UL_DEVICE Device, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        


    if (cacheMode == CACHE_MODE_THIS)
	{
		cacheResult += Device.activetechnology + "?";
		cacheResult += Device.description + "?";
		cacheResult += Device.headline + "?";
		cacheResult += Device.library + "?";
		cacheResult += Device.name + "?";
		cacheResult += Device.prefix + "?";
		cacheResult += Device.technologies + "?";
		cacheResult += Device.value + "?";
		return cacheResult;
	}
	else if (baseName == "activetechnology")
		return Device.activetechnology;
	else if (baseName == "area")
		return ULAreaHandler(Device.area,nextPath,argument,0);		
	else if (baseName == "description")
		return Device.description;
	else if (baseName == "headline")
		return Device.headline;
	else if (baseName == "library")
		return Device.library;
	else if (baseName == "name")
		return Device.name;
	else if (baseName == "package")
		return ULPackageHandler(Device.package,nextPath,argument,0);	
	else if (baseName == "prefix")
		return Device.prefix;
	else if (baseName == "technologies")
		return Device.technologies;
	else if (baseName == "value")
		return Device.value;
		
	string splitLoopMember[];
	int accessIndex=0,currentIndex=0;
	
	if (!isLastPath)
	{	
	    nextPath = GetNextPath(nextPath);
		strsplit(splitLoopMember,baseType,'^');
		accessIndex = strtol(splitLoopMember[1]);
	}

	if (baseName == "attributes"){
		Device.attributes(Attribute)  { 
			if (!isLastPath){ if (currentIndex  == accessIndex) { return ULAttributeHandler(Attribute, nextPath,argument,0); } }
			else if (nextCacheMode==CACHE_MODE_THIS) { cacheResult += ":" + ULAttributeHandler(Attribute, "", "",CACHE_MODE_THIS); } 
			currentIndex++;
		}
		if (nextCacheMode==CACHE_MODE_THIS) return cacheResult;
		else return intToStr(currentIndex);
	
	} else if (baseName == "gates"){
		Device.gates(Gate)  { 
			if (!isLastPath){ if (currentIndex  == accessIndex) { return ULGateHandler(Gate, nextPath,argument,0); } }
			else if (nextCacheMode==CACHE_MODE_THIS) { cacheResult += ":" + ULGateHandler(Gate, "", "",CACHE_MODE_THIS); } 
			currentIndex++;
		}
		if (nextCacheMode==CACHE_MODE_THIS) return cacheResult;
		else return intToStr(currentIndex);
	
	} 
	
	return "ERROR:" + intToStr(ERROR_DEVICE_HANDLER);
}
