/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULViaHandler.ulp generated on 17/17/13 13:16:03 */

#include "ULSupport.ulp"

string ULViaHandler(UL_VIA Via,string currentPath, string argument, char cacheMode)
{
	string baseName = GetFirstPathItem(currentPath);
	string nextPath = GetNextPath(currentPath);
	string baseType = GetFirstPathItem(nextPath);
	string cacheResult;

    if (cacheMode == CACHE_MODE_THIS)
	{
		cacheResult += intToStr(Via.drill) + "?";
		cacheResult += intToStr(Via.drillsymbol) + "?";
		cacheResult += intToStr(Via.end) + "?";
		cacheResult += intToStr(Via.flags) + "?";
		cacheResult += intToStr(Via.start) + "?";
		cacheResult += intToStr(Via.x) + "?";
		cacheResult += intToStr(Via.y) + "?";
		return cacheResult;
	}
	else if (baseName == "diameter")
	{
		int index = strtod(argument);
		return intToStr(Via.diameter[index]);
	}
	else if (baseName == "drill")
		return intToStr(Via.drill);
	else if (baseName == "drillsymbol")
		return intToStr(Via.drillsymbol);
	else if (baseName == "end")
		return intToStr(Via.end);
	else if (baseName == "flags")
		return intToStr(Via.flags);
	else if (baseName == "shape")
	{
		int index = strtod(argument);
		return intToStr(Via.shape[index]);
	}
	else if (baseName == "start")
		return intToStr(Via.start);
	else if (baseName == "x")
		return intToStr(Via.x);
	else if (baseName == "y")
		return intToStr(Via.y);
	
	return "ERROR:" + intToStr(ERROR_VIA_HANDLER);
}
