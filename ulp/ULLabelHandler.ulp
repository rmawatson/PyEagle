/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULLabelHandler.ulp generated on 17/17/13 13:16:03 */

#include "ULSupport.ulp"
#include "ULTextHandler.ulp"
#include "ULWireHandler.ulp"

string ULLabelHandler(UL_LABEL Label, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += realToStr(Label.angle) + "?";
		cacheResult += intToStr(Label.layer) + "?";
		cacheResult += intToStr(Label.mirror) + "?";
		cacheResult += intToStr(Label.spin) + "?";
		cacheResult += intToStr(Label.x) + "?";
		cacheResult += intToStr(Label.y) + "?";
		cacheResult += intToStr(Label.xref) + "?";
		return cacheResult;
	}
	else if (baseName == "angle")
		return realToStr(Label.angle);
	else if (baseName == "layer")
		return intToStr(Label.layer);
	else if (baseName == "mirror")
		return intToStr(Label.mirror);
	else if (baseName == "spin")
		return intToStr(Label.spin);
	else if (baseName == "text")
		return ULTextHandler(Label.text,nextPath,argument,0);		
	else if (baseName == "x")
		return intToStr(Label.x);	
	else if (baseName == "y")
		return intToStr(Label.y);
	else if (baseName == "xref")
		return intToStr(Label.xref);
		

	string splitLoopMember[];
	int accessIndex=0,currentIndex=0;
	
	if (!isLastPath)
	{	
	    nextPath = GetNextPath(nextPath);
		strsplit(splitLoopMember,baseType,'^');
		accessIndex = strtol(splitLoopMember[1]);
	}

	if (baseName == "wires"){
		Label.wires(Wire)  { 
			if (!isLastPath){ if (currentIndex  == accessIndex) { return ULWireHandler(Wire, nextPath,argument,0); } }
			else if (nextCacheMode==CACHE_MODE_THIS) { cacheResult += ":" + ULWireHandler(Wire, "", "",CACHE_MODE_THIS); } 
			currentIndex++;
		}
		if (nextCacheMode==CACHE_MODE_THIS) return cacheResult;
		else return intToStr(currentIndex);
	
	} 
	return "ERROR:" + intToStr(ERROR_LABEL_HANDLER);
}
