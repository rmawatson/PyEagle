/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULPinRefHandler.ulp generated on 17/17/13 13:16:03 */

#include "ULSupport.ulp"
#include "ULInstanceHandler.ulp"
#include "ULPartHandler.ulp"
#include "ULPinHandler.ulp"

string ULPinRefHandler(UL_PINREF PinRef, string currentPath, string argument, char cacheMode)
{
	string baseName = GetFirstPathItem(currentPath);
	string nextPath = GetNextPath(currentPath);
	string baseType = GetFirstPathItem(nextPath);

	/*if (baseName == "instance")
		return ULInstanceHandler(PinRef.instance,nextPath,argument,0);
	else */if (baseName == "contact")
		return ULPartHandler(PinRef.part,nextPath,argument,0);		
	else if (baseName == "direction")
		return ULPinHandler(PinRef.pin,nextPath,argument,0);	

	
	return "ERROR:" + intToStr(ERROR_PINREF_HANDLER);
}
