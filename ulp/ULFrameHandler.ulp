/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULFrameHandler.ulp generated on 17/17/13 13:16:03 */

#include "ULSupport.ulp"
#include "ULTextHandler.ulp"
#include "ULWireHandler.ulp"

string ULFrameHandler(UL_FRAME Frame,string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += intToStr(Frame.columns) + "?";
		cacheResult += intToStr(Frame.rows) + "?";
		cacheResult += intToStr(Frame.border) + "?";
		cacheResult += intToStr(Frame.x1) + "?";
		cacheResult += intToStr(Frame.x2) + "?";
		cacheResult += intToStr(Frame.y1) + "?";
		cacheResult += intToStr(Frame.y2) + "?";
		return cacheResult;
	}
	else if (baseName == "columns")
		return intToStr(Frame.columns);
	else if (baseName == "rows")
		return intToStr(Frame.rows);
	else if (baseName == "border")
		return intToStr(Frame.border);
	else if (baseName == "x1")
		return intToStr(Frame.x1);
	else if (baseName == "x2")
		return intToStr(Frame.x2);
	else if (baseName == "y1")
		return intToStr(Frame.y1);
	else if (baseName == "y2")
		return intToStr(Frame.y2);


	string splitLoopMember[];
	int accessIndex=0,currentIndex=0;
	
	if (!isLastPath)
	{	
	    nextPath = GetNextPath(nextPath);
		strsplit(splitLoopMember,baseType,'^');
		accessIndex = strtol(splitLoopMember[1]);
	}

	if (baseName == "texts"){
		Frame.texts(Text)  { 
			if (!isLastPath){ if (currentIndex  == accessIndex) { return ULTextHandler(Text, nextPath,argument,0); } }
			else if (nextCacheMode==CACHE_MODE_THIS) { cacheResult += ":" + ULTextHandler(Text, "", "",CACHE_MODE_THIS); } 
			currentIndex++;
		}
		if (nextCacheMode==CACHE_MODE_THIS) return cacheResult;
		else return intToStr(currentIndex);
	
	} else if (baseName == "fillings"){
		Frame.wires(Wire)  { 
			if (!isLastPath){ if (currentIndex  == accessIndex) { return ULWireHandler(Wire, nextPath,argument,0); } }
			else if (nextCacheMode==CACHE_MODE_THIS) { cacheResult += ":" + ULWireHandler(Wire, "", "",CACHE_MODE_THIS); } 
			currentIndex++;
		}
		if (nextCacheMode==CACHE_MODE_THIS) return cacheResult;
		else return intToStr(currentIndex);
	
	} 
	
	return "ERROR:" + intToStr(ERROR_FRAME_HANDLER);
}
