/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULPinHandler.ulp generated on 17/17/13 13:16:03 */

#include "ULSupport.ulp"
#include "ULCircleHandler.ulp"
#include "ULContactHandler.ulp"
#include "ULTextHandler.ulp"
#include "ULWireHandler.ulp"

string ULPinHandler(UL_PIN Pin, string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += realToStr(Pin.angle) + "?";
		cacheResult += intToStr(Pin.direction) + "?";
		cacheResult += intToStr(Pin.function) + "?";
		cacheResult += intToStr(Pin.length) + "?";
		cacheResult += Pin.name + "?";
		cacheResult += Pin.net + "?";
		cacheResult += intToStr(Pin.route) + "?";
		cacheResult += intToStr(Pin.swaplevel) + "?";
		cacheResult += intToStr(Pin.visible) + "?";
		cacheResult += intToStr(Pin.x) + "?";
		cacheResult += intToStr(Pin.y) + "?";
		return cacheResult;
	}
	else if (baseName == "angle")
		return realToStr(Pin.angle);
	else if (baseName == "direction")
		return intToStr(Pin.direction);
	else if (baseName == "function")
		return intToStr(Pin.function);
	else if (baseName == "length")
		return intToStr(Pin.length);
	else if (baseName == "name")
		return Pin.name;
	else if (baseName == "net")
		return Pin.net;
	else if (baseName == "route")
		return intToStr(Pin.route);
	else if (baseName == "swaplevel")
		return intToStr(Pin.swaplevel);
	else if (baseName == "visible")
		return intToStr(Pin.visible);
	else if (baseName == "x")
		return intToStr(Pin.x);
	else if (baseName == "y")
		return intToStr(Pin.y);
		
	string splitLoopMember[];
	int accessIndex=0,currentIndex=0;
	
	if (!isLastPath)
	{	
	    nextPath = GetNextPath(nextPath);
		strsplit(splitLoopMember,baseType,'^');
		accessIndex = strtol(splitLoopMember[1]);
	}

	if (baseName == "circles"){
		Pin.circles(Circle)  { 
			if (!isLastPath){ if (currentIndex  == accessIndex) { return ULCircleHandler(Circle, nextPath,argument,0); } }
			else if (nextCacheMode==CACHE_MODE_THIS) { cacheResult += ":" + ULCircleHandler(Circle, "", "",CACHE_MODE_THIS); } 
			currentIndex++;
		}
		if (nextCacheMode==CACHE_MODE_THIS) return cacheResult;
		else return intToStr(currentIndex);
	
	} else if (baseName == "contacts"){
		Pin.contacts(Contact)  { 
			if (!isLastPath){ if (currentIndex  == accessIndex) { return ULContactHandler(Contact, nextPath,argument,0); } }
			else if (nextCacheMode==CACHE_MODE_THIS) { cacheResult += ":" + ULContactHandler(Contact, "", "",CACHE_MODE_THIS); } 
			currentIndex++;
		}
		if (nextCacheMode==CACHE_MODE_THIS) return cacheResult;
		else return intToStr(currentIndex);
	
	} else if (baseName == "texts"){
		Pin.texts(Text)  { 
			if (!isLastPath){ if (currentIndex  == accessIndex) { return ULTextHandler(Text, nextPath,argument,0); } }
			else if (nextCacheMode==CACHE_MODE_THIS) { cacheResult += ":" + ULTextHandler(Text, "", "",CACHE_MODE_THIS); } 
			currentIndex++;
		}
		if (nextCacheMode==CACHE_MODE_THIS) return cacheResult;
		else return intToStr(currentIndex);
	
	} else if (baseName == "wires"){
		Pin.wires(Wire)  { 
			if (!isLastPath){ if (currentIndex  == accessIndex) { return ULWireHandler(Wire, nextPath,argument,0); } }
			else if (nextCacheMode==CACHE_MODE_THIS) { cacheResult += ":" + ULWireHandler(Wire, "", "",CACHE_MODE_THIS); } 
			currentIndex++;
		}
		if (nextCacheMode==CACHE_MODE_THIS) return cacheResult;
		else return intToStr(currentIndex);
	
	} 
	
	return "ERROR:" + intToStr(ERROR_PIN_HANDLER);
}
