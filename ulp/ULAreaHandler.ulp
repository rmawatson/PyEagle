/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULAreaHandler.ulp generated on 17/17/13 13:16:03 */

#include "ULSupport.ulp"

string ULAreaHandler(UL_AREA Area, string currentPath, string argument, char cacheMode)
{
	string baseName = GetFirstPathItem(currentPath);
	string nextPath = GetNextPath(currentPath);
	string baseType = GetFirstPathItem(nextPath);

	string cacheResult;

    if (cacheMode == CACHE_MODE_THIS)
	{
		cacheResult += intToStr(Area.x1) + "?";
		cacheResult += intToStr(Area.x2) + "?";
		cacheResult += intToStr(Area.y1) + "?";
		cacheResult += intToStr(Area.y2) + "?";
		return cacheResult;
	}
	else if (baseName == "x1")
		return intToStr(Area.x1);
	else if (baseName == "x2")
		return intToStr(Area.x2);
	else if (baseName == "y1")
		return intToStr(Area.y1);
	else if (baseName == "y2")
		return intToStr(Area.y2);

	return "ERROR:" + intToStr(ERROR_AREA_HANDLER);
}
