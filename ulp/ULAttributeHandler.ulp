/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULAttributeHandler.ulp generated on 17/17/13 13:16:03 */

#include "ULSupport.ulp"
#include "ULTextHandler.ulp"

string ULAttributeHandler(UL_ATTRIBUTE Attribute, string currentPath, string argument, char cacheMode)
{
	string baseName = GetFirstPathItem(currentPath);
	string nextPath = GetNextPath(currentPath);
	string baseType = GetFirstPathItem(nextPath);

	string cacheResult;

    if (cacheMode == CACHE_MODE_THIS)
	{
		cacheResult += intToStr(Attribute.constant) + "?";
		cacheResult += Attribute.defaultvalue + "?";
		cacheResult += intToStr(Attribute.display) + "?";
		cacheResult += Attribute.name + "?";
		cacheResult += Attribute.value + "?";
		return cacheResult;
	}
	else if (baseName == "constant")
		return intToStr(Attribute.constant);
	else if (baseName == "defaultvalue")
		return Attribute.defaultvalue;
	else if (baseName == "display")
		return intToStr(Attribute.display);
	else if (baseName == "name")
		return Attribute.name;
	else if (baseName == "text")
		return ULTextHandler(Attribute.text,currentPath,argument,0);
	else if (baseName == "value")
		return Attribute.value;
		
	return "ERROR:" + intToStr(ERROR_ATTRIBUTE_HANDLER);
}
