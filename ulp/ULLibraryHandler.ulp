/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULLibraryHandler.ulp generated on 17/17/13 13:16:03 */

#include "ULSupport.ulp"
#include "ULGridHandler.ulp"
#include "ULDeviceHandler.ulp"
#include "ULDeviceSetHandler.ulp"
#include "ULLayerHandler.ulp"
#include "ULPackageHandler.ulp"
#include "ULSymbolHandler.ulp"

string ULLibraryHandler(UL_LIBRARY Library, string currentPath, string argument, char cacheMode)
{
	

	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        
	
	string splitLoopMember[];
	int accessIndex=0,currentIndex=0;
	
	if (!isLastPath)
	{	
	    nextPath = GetNextPath(nextPath);
		strsplit(splitLoopMember,baseType,'^');
		accessIndex = strtol(splitLoopMember[1]);
	}

	
    if (cacheMode == CACHE_MODE_THIS)
	{
		cacheResult += Library.description + "?";
		cacheResult += Library.headline + "?";
		cacheResult += Library.name + "?";
		return cacheResult;
	}
	else if (baseName == "description")
		return Library.description;
	else if (baseName == "grid")
		return ULGridHandler(Library.grid,nextPath,argument,0);		
	else if (baseName == "headline")
		return Library.headline;
	else if (baseName == "name")
		return Library.name;


	if (baseName == "devices"){
		Library.devices(Device)  { 
			if (!isLastPath){ if (currentIndex  == accessIndex) { return ULDeviceHandler(Device, nextPath,argument,0); } }
			else if (nextCacheMode==CACHE_MODE_THIS) { cacheResult += ":" + ULDeviceHandler(Device, "", "",CACHE_MODE_THIS); } 
			currentIndex++;
		}
		if (nextCacheMode==CACHE_MODE_THIS) return cacheResult;
		else return intToStr(currentIndex);
	
	} else if (baseName == "devicesets"){
		Library.devicesets(DeviceSet)  { 
			if (!isLastPath){ if (currentIndex  == accessIndex) { return ULDeviceSetHandler(DeviceSet, nextPath,argument,0); } }
			else if (nextCacheMode==CACHE_MODE_THIS) { cacheResult += ":" + ULDeviceSetHandler(DeviceSet, "", "",CACHE_MODE_THIS); } 
			currentIndex++;
		}
		if (nextCacheMode==CACHE_MODE_THIS) return cacheResult;
		else return intToStr(currentIndex);
	
	}  else if (baseName == "layers"){
		Library.layers(Layer)  { 
			if (!isLastPath){ if (currentIndex  == accessIndex) { return ULLayerHandler(Layer, nextPath,argument,0); } }
			else if (nextCacheMode==CACHE_MODE_THIS) { cacheResult += ":" + ULLayerHandler(Layer, "", "",CACHE_MODE_THIS); } 
			currentIndex++;
		}
		if (nextCacheMode==CACHE_MODE_THIS) return cacheResult;
		else return intToStr(currentIndex);
	
	} else if (baseName == "packages"){
		Library.packages(Package)  { 
			if (!isLastPath){ if (currentIndex  == accessIndex) { return ULPackageHandler(Package, nextPath,argument,0); } }
			else if (nextCacheMode==CACHE_MODE_THIS) { cacheResult += ":" + ULPackageHandler(Package, "", "",CACHE_MODE_THIS); } 
			currentIndex++;
		}
		if (nextCacheMode==CACHE_MODE_THIS) return cacheResult;
		else return intToStr(currentIndex);
	
	} else if (baseName == "symbols"){
		Library.symbols(Symbol)  { 
			if (!isLastPath){ if (currentIndex  == accessIndex) { return ULSymbolHandler(Symbol, nextPath,argument,0); } }
			else if (nextCacheMode==CACHE_MODE_THIS) { cacheResult += ":" + ULSymbolHandler(Symbol, "", "",CACHE_MODE_THIS); } 
			currentIndex++;
		}
		if (nextCacheMode==CACHE_MODE_THIS) return cacheResult;
		else return intToStr(currentIndex);

	}
	
	return "ERROR:" + intToStr(ERROR_LIBRARY_HANDLER);
}
