/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULContactHandler.ulp generated on 17/17/13 13:16:03 */

#include "ULSupport.ulp"
#include "ULPadHandler.ulp"
#include "ULSmdHandler.ulp"
#include "ULPolygonHandler.ulp"
#include "ULWireHandler.ulp"

string ULContactHandler(UL_CONTACT Contact,string currentPath, string argument, char cacheMode)
{
	string baseName   = GetFirstPathItem(currentPath);
	string nextPath   = GetNextPath(currentPath);
	string baseType = GetFirstPathItem(nextPath);
	char isLastPath = nextPath ? 0 : 1;

    char   nextCacheMode = cacheMode;
    string cacheResult;

    if (cacheMode==CACHE_MODE_AHEAD && isLastPath)
        nextCacheMode = CACHE_MODE_THIS;
                        

    if (cacheMode == CACHE_MODE_THIS)
	{
		cacheResult += Contact.name + "?";
		cacheResult += Contact.signal + "?";
		cacheResult += intToStr(Contact.x) + "?";
		cacheResult += intToStr(Contact.y) + "?";
		return cacheResult;
	}
	else if (baseName == "name")
		return Contact.name;
	else if (baseName == "pad")
		return ULPadHandler(Contact.pad,nextPath, argument,0);
	else if (baseName == "signal")
		return Contact.signal;
	else if (baseName == "smd")
		return ULSmdHandler(Contact.smd,nextPath, argument,0);
	else if (baseName == "x")
		return intToStr(Contact.x);
	else if (baseName == "y")
		return intToStr(Contact.y);
		
	string splitLoopMember[];
	int accessIndex=0,currentIndex=0;
	
	if (!isLastPath)
	{	
	    nextPath = GetNextPath(nextPath);
		strsplit(splitLoopMember,baseType,'^');
		accessIndex = strtol(splitLoopMember[1]);
	}

	if (baseName == "polygons"){
		Contact.polygons(Polygon)  { 
			if (!isLastPath){ if (currentIndex  == accessIndex) { return ULPolygonHandler(Polygon, nextPath,argument,0); } }
			else if (nextCacheMode==CACHE_MODE_THIS) { cacheResult += ":" + ULPolygonHandler(Polygon, "", "",CACHE_MODE_THIS); } 
			currentIndex++;
		}
		if (nextCacheMode==CACHE_MODE_THIS) return cacheResult;
		else return intToStr(currentIndex);
	
	} else if (baseName == "wires"){
		Contact.wires(Wire)  { 
			if (!isLastPath){ if (currentIndex  == accessIndex) { return ULWireHandler(Wire, nextPath,argument,0); } }
			else if (nextCacheMode==CACHE_MODE_THIS) { cacheResult += ":" + ULWireHandler(Wire, "", "",CACHE_MODE_THIS); } 
			currentIndex++;
		}
		if (nextCacheMode==CACHE_MODE_THIS) return cacheResult;
		else return intToStr(currentIndex);
	
	}
	
	return "ERROR:" + intToStr(ERROR_CONTACT_HANDLER);
}
