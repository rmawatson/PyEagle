/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULHoleHandler.ulp generated on 17/17/13 13:16:03 */

#include "ULSupport.ulp"

string ULHoleHandler(UL_HOLE Hole,string currentPath, string argument, char cacheMode)
{
	string baseName = GetFirstPathItem(currentPath);
	string nextPath = GetNextPath(currentPath);
	string baseType = GetFirstPathItem(nextPath);
	string cacheResult;

    if (cacheMode == CACHE_MODE_THIS)
	{
		cacheResult += intToStr(Hole.drill) + "?";
		cacheResult += intToStr(Hole.drillsymbol) + "?";
		cacheResult += intToStr(Hole.x) + "?";
		cacheResult += intToStr(Hole.y) + "?";
		return cacheResult;
	}
	else if (baseName == "diameter")
	{
		int index = strtod(argument);
		return intToStr(Hole.diameter[index]);
	}
	else if (baseName == "drill")
		return intToStr(Hole.drill);
	else if (baseName == "drillsymbol")
		return intToStr(Hole.drillsymbol);
	else if (baseName == "x")
		return intToStr(Hole.x);
	else if (baseName == "y")
		return intToStr(Hole.y);
	
	return "ERROR:" + intToStr(ERROR_FRAME_HANDLER);
}
