/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULBoardHandler.ulp generated on 17/17/13 13:16:03 */

#include "ULSupport.ulp"
#include "ULAreaHandler.ulp"
#include "ULGridHandler.ulp"
#include "ULAttributeHandler.ulp"
#include "ULCircleHandler.ulp"
#include "ULClassHandler.ulp"
#include "ULDimensionHandler.ulp"
#include "ULElementHandler.ulp"
#include "ULFrameHandler.ulp"
#include "ULHoleHandler.ulp"
#include "ULLayerHandler.ulp"
#include "ULLibraryHandler.ulp"
#include "ULPolygonHandler.ulp"
#include "ULRectangleHandler.ulp"
#include "ULSignalHandler.ulp"
#include "ULTextHandler.ulp"
#include "ULVariantDefHandler.ulp"
#include "ULWireHandler.ulp"

string ULBoardHandler(UL_BOARD Board,string currentPath, string argument, char cacheMode)
{
	string baseName   = GetFirstPathItem(currentPath);
	string nextPath   = GetNextPath(currentPath);
	string baseType   = GetFirstPathItem(nextPath);
	char isLastPath = nextPath ? 0 : 1;

	char   nextCacheMode = cacheMode;
	string cacheResult;

	if (cacheMode==CACHE_MODE_AHEAD && isLastPath)
		nextCacheMode = CACHE_MODE_THIS;


	string splitLoopMember[];
	int accessIndex=0,currentIndex=0;
	
	
	if (!isLastPath)
	{	
	    nextPath = GetNextPath(nextPath);
		strsplit(splitLoopMember,baseType,'^');
		accessIndex = strtol(splitLoopMember[1]);
	}

    if (cacheMode == CACHE_MODE_THIS)
	{
		cacheResult += escapeStr(Board.description) + "?";
		cacheResult += escapeStr(Board.headline) + "?";
		cacheResult += escapeStr(Board.name) + "?";
		return cacheResult;
	}
	else if (baseName == "area")
		return ULAreaHandler(Board.area,nextPath,argument,0);	
	else if (baseName == "description")
		return escapeStr(Board.description);
	else if (baseName == "grid")	
		return ULGridHandler(Board.grid,nextPath,argument,0);			
	else if (baseName == "headline")
		return escapeStr(Board.headline);
	else if (baseName == "name")
		return escapeStr(Board.name);



	
	if (baseName == "attributes"){
		Board.attributes(Attribute)  { 
			if (!isLastPath){ if (currentIndex  == accessIndex) { return ULAttributeHandler(Attribute, nextPath,argument,0); } }
			else if (nextCacheMode==CACHE_MODE_THIS) { cacheResult += ":" + ULAttributeHandler(Attribute, "", "",CACHE_MODE_THIS); } 
			currentIndex++;
		}
		if (nextCacheMode==CACHE_MODE_THIS) return cacheResult;
		else return intToStr(currentIndex);
	
	} else if (baseName == "circles"){
		Board.circles(Circle)  { 
			if (!isLastPath){ if (currentIndex  == accessIndex) { return ULCircleHandler(Circle, nextPath,argument,0); } }
			else if (nextCacheMode==CACHE_MODE_THIS) { cacheResult += ":" + ULCircleHandler(Circle, "", "",CACHE_MODE_THIS); } 
			currentIndex++;
		}
		if (nextCacheMode==CACHE_MODE_THIS) return cacheResult;
		else return intToStr(currentIndex);
	
	} else if (baseName == "classes"){
		Board.classes(Class)  { 
			if (!isLastPath){ if (currentIndex  == accessIndex) { return ULClassHandler(Class, nextPath,argument,0); } }
			else if (nextCacheMode==CACHE_MODE_THIS) { cacheResult += ":" + ULClassHandler(Class, "", "",CACHE_MODE_THIS); } 
			currentIndex++;
		}
		if (nextCacheMode==CACHE_MODE_THIS) return cacheResult;
		else return intToStr(currentIndex);
	
	} else if (baseName == "dimensions"){
		Board.dimensions(Dimension)  { 
			if (!isLastPath){ if (currentIndex  == accessIndex) { return ULDimensionHandler(Dimension, nextPath,argument,0); } }
			else if (nextCacheMode==CACHE_MODE_THIS) { cacheResult += ":" + ULDimensionHandler(Dimension, "", "",CACHE_MODE_THIS); } 
			currentIndex++;
		}
		if (nextCacheMode==CACHE_MODE_THIS) return cacheResult;
		else return intToStr(currentIndex);
	
	} else if (baseName == "elements"){
		Board.elements(Element)  { 
			if (!isLastPath){ if (currentIndex  == accessIndex) { return ULElementHandler(Element, nextPath,argument,0); } }
			else if (nextCacheMode==CACHE_MODE_THIS) { cacheResult += ":" + ULElementHandler(Element, "", "",CACHE_MODE_THIS); } 
			currentIndex++;
		}
		if (nextCacheMode==CACHE_MODE_THIS) return cacheResult;
		else return intToStr(currentIndex);
	
	} else if (baseName == "frames"){
		Board.frames(Frame)  { 
			if (!isLastPath){ if (currentIndex  == accessIndex) { return ULFrameHandler(Frame, nextPath,argument,0); } }
			else if (nextCacheMode==CACHE_MODE_THIS) { cacheResult += ":" + ULFrameHandler(Frame, "", "",CACHE_MODE_THIS); } 
			currentIndex++;
		}
		if (nextCacheMode==CACHE_MODE_THIS) return cacheResult;
		else return intToStr(currentIndex);
	
	} else if (baseName == "holes"){
		Board.holes(Hole)  { 
			if (!isLastPath){ if (currentIndex  == accessIndex) { return ULHoleHandler(Hole, nextPath,argument,0); } }
			else if (nextCacheMode==CACHE_MODE_THIS) { cacheResult += ":" + ULHoleHandler(Hole, "", "",CACHE_MODE_THIS); } 
			currentIndex++;
		}
		if (nextCacheMode==CACHE_MODE_THIS) return cacheResult;
		else return intToStr(currentIndex);
	
	} else if (baseName == "layers"){
		Board.layers(Layer)  { 
			if      (!isLastPath){ if (currentIndex  == accessIndex) { return ULLayerHandler(Layer, nextPath,argument,0); }}
			else if (nextCacheMode==CACHE_MODE_THIS) { cacheResult += ":" + ULLayerHandler(Layer, "","",CACHE_MODE_THIS); }
			currentIndex++;
		}
		if (nextCacheMode==CACHE_MODE_THIS) return cacheResult;
		else return intToStr(currentIndex);
	} else if (baseName == "libraries"){
		Board.libraries(Library)  { 
			if (!isLastPath){ if (currentIndex  == accessIndex) { return ULLibraryHandler(Library, nextPath,argument,0); } }
			else if (nextCacheMode==CACHE_MODE_THIS) { cacheResult += ":" + ULLibraryHandler(Library, "", "",CACHE_MODE_THIS); } 
			currentIndex++;
		}
		if (nextCacheMode==CACHE_MODE_THIS) return cacheResult;
		else return intToStr(currentIndex);
	
	} else if (baseName == "polygons"){
		Board.polygons(Polygon)  { 
			if (!isLastPath){ if (currentIndex  == accessIndex) { return ULPolygonHandler(Polygon, nextPath,argument,0); } }
			else if (nextCacheMode==CACHE_MODE_THIS) { cacheResult += ":" + ULPolygonHandler(Polygon, "", "",CACHE_MODE_THIS); } 
			currentIndex++;
		}
		if (nextCacheMode==CACHE_MODE_THIS) return cacheResult;
		else return intToStr(currentIndex);
	
	} else if (baseName == "rectangles"){
		Board.rectangles(Rectangle)  { 
			if (!isLastPath){ if (currentIndex  == accessIndex) { return ULRectangleHandler(Rectangle, nextPath,argument,0); } }
			else if (nextCacheMode==CACHE_MODE_THIS) { cacheResult += ":" + ULRectangleHandler(Rectangle, "", "",CACHE_MODE_THIS); } 
			currentIndex++;
		}
		if (nextCacheMode==CACHE_MODE_THIS) return cacheResult;
		else return intToStr(currentIndex);
	
	} else if (baseName == "signals"){
		Board.signals(Signal)  { 
			if (!isLastPath){ if (currentIndex  == accessIndex) { return ULSignalHandler(Signal, nextPath,argument,0); } }
			else if (nextCacheMode==CACHE_MODE_THIS) { cacheResult += ":" + ULSignalHandler(Signal, "", "",CACHE_MODE_THIS); } 
			currentIndex++;
		}
		if (nextCacheMode==CACHE_MODE_THIS) return cacheResult;
		else return intToStr(currentIndex);
	
	} else if (baseName == "texts"){
		Board.texts(Text)  { 
			if (!isLastPath){ if (currentIndex  == accessIndex) { return ULTextHandler(Text, nextPath,argument,0); } }
			else if (nextCacheMode==CACHE_MODE_THIS) { cacheResult += ":" + ULTextHandler(Text, "", "",CACHE_MODE_THIS); } 
			currentIndex++;
		}
		if (nextCacheMode==CACHE_MODE_THIS) return cacheResult;
		else return intToStr(currentIndex);
	
	} else if (baseName == "variantdefs"){
		Board.variantdefs(VariantDef)  { 
			if (!isLastPath){ if (currentIndex  == accessIndex) { return ULVariantDefHandler(VariantDef, nextPath,argument,0); } }
			else if (nextCacheMode==CACHE_MODE_THIS) { cacheResult += ":" + ULVariantDefHandler(VariantDef, "", "",CACHE_MODE_THIS); } 
			currentIndex++;
		}
		if (nextCacheMode==CACHE_MODE_THIS) return cacheResult;
		else return intToStr(currentIndex);
	
	} else if (baseName == "wires"){
		Board.wires(Wire)  { 
			if (!isLastPath){ if (currentIndex  == accessIndex) { return ULWireHandler(Wire, nextPath,argument,0); } }
			else if (nextCacheMode==CACHE_MODE_THIS) { cacheResult += ":" + ULWireHandler(Wire, "", "",CACHE_MODE_THIS); } 
			currentIndex++;
		}
		if (nextCacheMode==CACHE_MODE_THIS) return cacheResult;
		else return intToStr(currentIndex);
	
	}
	return "ERROR:" + intToStr(ERROR_BOARD_HANDLER);

}
