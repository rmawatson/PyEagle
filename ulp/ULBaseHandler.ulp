/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULBaseHandler.ulp generated on 17/17/13 13:16:03 */

#include "ULSupport.ulp"
#include "ULBoardHandler.ulp"
#include "ULSchematicHandler.ulp"
#include "ULSheetHandler.ulp"
#include "ULLibraryHandler.ulp"
#include "ULPackageHandler.ulp"

string ULBaseHandler(string currentPath, string argument, char cacheMode)
{

	DebugPrintStr(currentPath);
	string baseName   = GetFirstPathItem(currentPath);
	string nextPath   = GetNextPath(currentPath);

	if (baseName == "ULBoard") {
		if (board){
			board(Board) { return ULBoardHandler(Board,nextPath,argument,cacheMode); }
		} else {
			return "ERROR:" + intToStr(ERROR_INVALID_CONTEXT);
		}
	}
	else if (baseName == "ULSchematic") {
		if (schematic) {
			schematic(Schematic) { return ULSchematicHandler(Schematic,nextPath,argument,cacheMode); }
		} else {
			return "ERROR:" + intToStr(ERROR_INVALID_CONTEXT);
		}
	}
	else if (baseName == "ULSheet") {
		if (sheet){
			sheet(Sheet) { return ULSheetHandler(Sheet,nextPath,argument,cacheMode); }
		} else {
			return "ERROR:" + intToStr(ERROR_INVALID_CONTEXT);
		}
	}
	else if (baseName == "ULLibrary") {
		if (library){
			library(Library) { return ULLibraryHandler(Library,nextPath,argument,cacheMode); }
		} else {
			return "ERROR:" + intToStr(ERROR_INVALID_CONTEXT);
		}
	}
	else if (baseName == "ULPackage") {
		if (package){
			package(Package) { return ULPackageHandler(Package,nextPath,argument,cacheMode); }
		} else {
			return "ERROR:" + intToStr(ERROR_INVALID_CONTEXT);
		}
	}
	
	return "ERROR:" + intToStr(ERROR_BASE_HANDLER);
}
