/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULGridHandler.ulp generated on 17/17/13 13:16:03 */

#include "ULSupport.ulp"

string ULGridHandler(UL_GRID Grid,string currentPath, string argument, char cacheMode)
{
	string baseName = GetFirstPathItem(currentPath);
	string nextPath = GetNextPath(currentPath);
	string baseType = GetFirstPathItem(nextPath);
	char isLastPath = nextPath ? 0 : 1;

	char   nextCacheMode = cacheMode;
	string cacheResult;

	DebugPrintInt(isLastPath);
	
	if (cacheMode==CACHE_MODE_AHEAD && isLastPath)
		nextCacheMode = CACHE_MODE_THIS;


	string splitLoopMember[];
	int accessIndex=0,currentIndex=0; 
	
	
	if (!isLastPath)
	{	
	    nextPath = GetNextPath(nextPath);
		strsplit(splitLoopMember,baseType,'^');
		accessIndex = strtol(splitLoopMember[1]);
	}

	
    if (cacheMode == CACHE_MODE_THIS)
	{
		cacheResult += realToStr(Grid.distance) + "?";
		cacheResult += intToStr(Grid.dots) + "?";
		cacheResult += intToStr(Grid.multiple) + "?";
		cacheResult += intToStr(Grid.on) + "?";
		cacheResult += intToStr(Grid.unit) + "?";
		cacheResult += intToStr(Grid.unitdist) + "?";
		return cacheResult;
	}
	else if (baseName == "distance")
		return realToStr(Grid.distance);
	else if (baseName == "dots")
		return intToStr(Grid.dots);
	else if (baseName == "multiple")
		return intToStr(Grid.multiple);
	else if (baseName == "on")
		return intToStr(Grid.on);
	else if (baseName == "unit")
		return intToStr(Grid.unit);
	else if (baseName == "unitdist")
		return intToStr(Grid.unitdist);

	return "ERROR:" + intToStr(ERROR_GRID_HANDLER);
}
