/*
 (C) Copyright 2013 Rob Watson rmawatson [at] hotmail.com  and others.

 All rights reserved. This program and the accompanying materials
 are made available under the terms of the GNU Lesser General Public License
 (LGPL) version 2.1 which accompanies this distribution, and is available at
 http://www.gnu.org/licenses/lgpl-2.1.html

 This library is distributed in the hope that it will be useful,
 but WITHOUT ANY WARRANTY; without even the implied warranty of
 MERCHANTABILITY or FITNESS FOR A PARTICULAR PURPOSE. See the GNU
 Lesser General Public License for more details.

 Contributors:
     Rob Watson ( rmawatson [at] hotmail )
*/

/* ULSmdHandler.ulp generated on 17/17/13 13:16:03 */

#include "ULSupport.ulp"

string ULSmdHandler(UL_SMD Smd,string currentPath, string argument, char cacheMode)
{
	string baseName   = GetFirstPathItem(currentPath);
	string nextPath   = GetNextPath(currentPath);
	string baseType = GetFirstPathItem(nextPath);
	string cacheResult;

    if (cacheMode == CACHE_MODE_THIS)
	{
		cacheResult += realToStr(Smd.angle) + "?";
		cacheResult += intToStr(Smd.flags) + "?";
		cacheResult += intToStr(Smd.layer) + "?";
		cacheResult += Smd.name + "?";
		cacheResult += intToStr(Smd.roundness) + "?";
		cacheResult += Smd.signal + "?";
		cacheResult += intToStr(Smd.x) + "?";
		cacheResult += intToStr(Smd.y) + "?";
		return cacheResult;
	}
	else if (baseName == "angle")
		return realToStr(Smd.angle);
	else if (baseName == "dx")
	{
		int index = strtol(argument);
		return intToStr(Smd.dx[index]);
	}
	else if (baseName == "dy")
	{
		int index = strtol(argument);
		return intToStr(Smd.dy[index]);
	}
	else if (baseName == "flags")
		return intToStr(Smd.flags);	
	else if (baseName == "layer")
		return intToStr(Smd.layer);
	else if (baseName == "name")
		return Smd.name;
	else if (baseName == "roundness")
		return intToStr(Smd.roundness);			
	else if (baseName == "signal")
		return Smd.signal;
	else if (baseName == "x")
		return intToStr(Smd.x);		
	else if (baseName == "y")
		return intToStr(Smd.y);
		
	return "ERROR:" + intToStr(ERROR_PAD_HANDLER);
}
